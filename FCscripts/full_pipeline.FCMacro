import FreeCAD as App
import FreeCADGui as Gui
import Part, Draft
import math
import os
from PySide2.QtWidgets import QFileDialog

# Global variables
doc = None
# Constants for the engraving
TRI_HEIGHT = 0.2  # Height of the triangle [mm]
TRI_ANGLE = math.pi / 2  # Angle of the tip [rad]
CYL_RADIUS = 26.5  # Radius of the cylinder [mm]
CYL_LENGTH = 125  # Length of the cylinder [mm]
PATH_FILLET_RADIUS = 0.5 # Radius of the fillet to smooth tip path
TIP_FILLET_RADIUS = 0.010 # Radius of the bottom of the engraving

def cyl_to_cart(r, theta, z):
    """Convert cylindrical coordinates to cartesian"""
    x = r * math.cos(theta)
    y = r * math.sin(theta)
    return (x, y, z)

def cart_to_cyl(x, y, z):
    """Convert cartesian coordinates to cylindrical"""
    r = math.sqrt(x*x + y*y)
    theta = math.atan2(y, x)
    return (r, theta)

def create_cylinder(radius, length):
    """Create a cylinder with given radius and length"""
    cylinder = Part.makeCylinder(radius, length)
    cylinder_obj = doc.addObject("Part::Feature", "Cylinder")
    cylinder_obj.Shape = cylinder
    return cylinder_obj

def create_triangle_profile(tip_point, next_point):
    """Create triangular profile for the engraving"""
    tip_x, tip_y, tip_z = tip_point
    _, theta = cart_to_cyl(tip_x, tip_y, tip_z)
    
    # Create base triangle with tip at the origin, on yz plane    
    top_x, top_y, top_z = TRI_HEIGHT, 0,  TRI_HEIGHT * math.tan(TRI_ANGLE / 2)
    bot_x, bot_y, bot_z = TRI_HEIGHT, 0, -TRI_HEIGHT * math.tan(TRI_ANGLE / 2)

    # Rotate triangle around x axis
    dx, dy, dz = next_point[0] - tip_x, next_point[1] - tip_y, next_point[2] - tip_z
    angle = -math.atan2(dz, math.sqrt(dx**2 + dy**2))
    top_y, top_z = -top_z * math.sin(angle), top_z * math.cos(angle)
    bot_y, bot_z = -top_y, -top_z

    # Rotate the triangle around z axis
    top_x, top_y = top_x * math.cos(theta) - top_y * math.sin(theta), top_x * math.sin(theta) + top_y * math.cos(theta)
    bot_x, bot_y = bot_x * math.cos(theta) - bot_y * math.sin(theta), bot_x * math.sin(theta) + bot_y * math.cos(theta)

    # Translate the triangle to the tip
    top_x += tip_x
    top_y += tip_y
    top_z += tip_z
    bot_x += tip_x
    bot_y += tip_y
    bot_z += tip_z

    # Create triangle wire
    v1 = App.Vector(tip_x, tip_y, tip_z)
    v2 = App.Vector(top_x, top_y, top_z)
    v3 = App.Vector(bot_x, bot_y, bot_z)
    
    wire = Draft.make_wire([v1, v2, v3, v1])
    wire.FilletRadius = TIP_FILLET_RADIUS
    return wire

def create_tip_path(points):
    """Create the path for the engraving tip"""
    # edges = [Draft.make_line(points[i], points[i+1]) for i in range(len(points)-1)]
    # filleted = round_corners(edges, FILLET_RADIUS)
    path = Draft.make_wire(points)
    # path.FilletRadius = PATH_FILLET_RADIUS
    return path

# def round_corners(edges, radius):
#     """Rounds the corners of a Part.Wire with a given radius"""

#     print("type of edges[0]:\t", edges[0], type(edges[0]), edges[0].__dict__)
#     # edges = [e.toShape() for e in edges]
#     edges = edges[:2]

#     # Create a list of edges
#     print("edges:\t", edges)
#     filleted = Draft.make_fillet(edges, radius)
#     print("filleted:", filleted)
#     return filleted
    
    # # Create a list of fillets
    # fillets = []
    # for edge in edges:
    #     fillet = edge.makeFillet(radius)
    #     fillets.append(fillet)
    
    # # Create a list of vertices
    # vertices = []
    # for fillet in fillets:
    #     vertices.extend(fillet.Vertexes)
    
    # # Create a new wire
    # new_wire = wire.toShape().makeFillets(radius, edges)
    # return new_wire

def engrave_once(file_path, loop_id):
    """Create one engraving loop"""
    points = []
    with open(file_path, 'r') as f:
        for line in f:
            x, y, z = map(float, line.strip().split(','))
            points.append(App.Vector(x*1e3, y*1e3, z*1e3))

    # Create path wire
    path_obj = create_tip_path(points)
    # path_obj = doc.addObject("Part::Feature", f"Loop_{loop_id}")
    # path_obj.Shape = path_wire

    # Create triangle profile
    # profile_obj = create_triangle_profile(points[-1], points[-2])
    # profile_obj = doc.addObject("Part::Feature", f"Triangle_{loop_id}")
    # profile_obj.Shape = profile_wire

    # # Create sweep
    # sweep_obj = doc.addObject("Part::Sweep", f"Sweep_{loop_id}")
    # sweep_obj.Sections = [profile_obj]  # Use the document object
    # sweep_obj.Spine = (path_obj, [])  # Use the document object
    # sweep_obj.Solid = True
    # sweep_obj.Frenet = True
    # sweep_obj.recompute()

    # return sweep_obj

def engrave_all(folder_path):
    """Create all engraving loops"""
    whole_sweep = None
    for i, filename in enumerate(sorted(os.listdir(folder_path))):
        if filename.endswith('.csv'):
            file_path = os.path.join(folder_path, filename)
            print(f"Processing file {filename}")

            # Create the engraving loop segment
            new_sweep = engrave_once(file_path, loop_id=i)

            # Merge the new segment with the previous ones
    #         if whole_sweep:
    #             fuse_obj = doc.addObject("Part::Fuse", f"MergedSweep_{i}")
    #             fuse_obj.Base = whole_sweep
    #             fuse_obj.Tool = new_sweep
    #             doc.recompute()
    #             whole_sweep = fuse_obj
    #         else:
    #             whole_sweep = new_sweep

    # # Engrave the cylinder with whole loop
    # cut_obj = doc.addObject("Part::Cut", f"EngravedCylinder")
    # cut_obj.Base = doc.getObject("Cylinder")
    # cut_obj.Tool = whole_sweep
    # doc.recompute()

def select_folder():
    """Open folder selection dialog"""
    folder = QFileDialog.getExistingDirectory()
    return folder if folder else None

def main():
    """Main function"""
    global doc
    
    # Create new document
    doc = App.newDocument()

    print("-"*10 + " Generating engraved cylinder " + "-"*10)
    
    # Create base cylinder
    #create_cylinder(CYL_RADIUS, CYL_LENGTH)
    
    # Get folder with CSV files
    folder_path = select_folder()
    if not folder_path:
        print("No folder selected")
        return
    
    # Process all CSV files
    engrave_all(folder_path)
    
    doc.recompute()
    Gui.SendMsgToActiveView("ViewFit")

if __name__ == '__main__':
    main()
