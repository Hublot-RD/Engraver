import FreeCAD as App
import Part
import math
import numpy as np
from FreeCAD import Base

def cyl2cart(r, phi, z):
    """Convert cylindrical coordinates to cartesian"""
    x = r * math.cos(phi)
    y = r * math.sin(phi)
    return (x, y, z)

def midpoint(p1, p2):
    """Calculate midpoint between two points in cylindrical coordinates"""
    r = (p1[0] + p2[0]) / 2
    phi = (p1[1] + p2[1]) / 2
    z = (p1[2] + p2[2]) / 2
    return (r, phi, z)

def create_cylinder(r, l):
    """Create a cylinder with given radius and length"""
    return Part.makeCylinder(r, l)

def create_triangle_for_edge(tip_path, angle):
    """Create a triangle for edge engraving"""
    h = 10  # height of the triangle
    dz = h * math.tan(math.radians(angle/2))
    
    start_tip, end_tip = tip_path
    _, phi, _ = midpoint(start_tip, end_tip)
    
    # Create triangle points
    t = Base.Vector(*cyl2cart(0, 0, 0))
    bh = Base.Vector(*cyl2cart(h, phi, dz))
    bl = Base.Vector(*cyl2cart(h, phi, -dz))
    
    # Move triangle to start position
    start_tip_cart = Base.Vector(*cyl2cart(*start_tip))
    t = t.add(start_tip_cart)
    bh = bh.add(start_tip_cart)
    bl = bl.add(start_tip_cart)
    
    # Create face
    wire = Part.makePolygon([t, bh, bl, t])
    face = Part.Face(wire)
    return face

def create_triangle_for_corner(tip_path, angle):
    """Create a triangle for corner engraving"""
    h = 10
    dz = h * math.tan(math.radians(angle/2))
    
    left, corner, _ = tip_path
    _, phi, _ = midpoint(left, corner)
    
    t = Base.Vector(*cyl2cart(0, 0, 0))
    bh = Base.Vector(*cyl2cart(h, phi, dz))
    bl = Base.Vector(*cyl2cart(h, phi, -dz))
    
    corner_cart = Base.Vector(*cyl2cart(*corner))
    t = t.add(corner_cart)
    bh = bh.add(corner_cart)
    bl = bl.add(corner_cart)
    
    wire = Part.makePolygon([t, bh, bl, t])
    face = Part.Face(wire)
    return face

def create_engraved_cylinder(R, L, angle, tip_path, filename="EngravedCylinder"):
    """Create an engraved cylinder"""
    # Create document
    doc = App.newDocument()
    
    # Create base cylinder
    cylinder = create_cylinder(R, L)
    
    # Process each segment of the path
    for i in range(len(tip_path) - 2):
        print(f"Starting segment {i+1}/{len(tip_path) - 2} ({round(100*(i+1)/(len(tip_path) - 2), 2)} %)")
        edge = [tip_path[i], tip_path[i+1], tip_path[i+2]]
        
        # Create and extrude triangle for edge
        triangle = create_triangle_for_edge(edge[:-1], angle)
        start_point = Base.Vector(*cyl2cart(*edge[0]))
        end_point = Base.Vector(*cyl2cart(*edge[1]))
        direction = end_point.sub(start_point)
        extrusion = triangle.extrude(direction)
        cylinder = cylinder.cut(extrusion)
        
        # Create and revolve triangle for corner
        #corner_triangle = create_triangle_for_corner(edge, angle)
        #corner_point = Base.Vector(*cyl2cart(*edge[1]))
        #angle_rad = (edge[2][1] - edge[0][1]) / 2
        #revolution = corner_triangle.revolve(corner_point, Base.Vector(0,0,1), math.degrees(angle_rad))
        #Part.show(revolution)
        #cylinder = cylinder.cut(revolution)
    
    # Process final edge
    final_triangle = create_triangle_for_edge([tip_path[-2], tip_path[-1]], angle)
    start_point = Base.Vector(*cyl2cart(*tip_path[-2]))
    end_point = Base.Vector(*cyl2cart(*tip_path[-1]))
    direction = end_point.sub(start_point)
    final_extrusion = final_triangle.extrude(direction)
    cylinder = cylinder.cut(final_extrusion)
    
    # Create final part
    Part.show(cylinder)
    doc.recompute()
    
    # Rename the object
    doc.ActiveObject.Label = filename
    
    # Export to STEP if needed
    if filename.endswith('.stp'):
        doc.ActiveObject.Shape.exportStep(filename)
    
    return doc.ActiveObject

# Example usage
if __name__ == '__main__':
    # Define parameters
    R = 28.0  # Radius
    L = 120.0  # Length
    depth = 0.05  # Depth of the cut [mm]
    angle = 90.0  # Angle of the cut
    pitch = 3  # Pitch of the spiral [mm]
    end_margin = 50  # Non engraved margin at each end
    
    # Create spiral path
    t_values = np.linspace(0, L-2*end_margin, 1000)
    path_points = [(R-depth, t/pitch*math.pi, t+end_margin) for t in t_values]
    
    # Create the engraved cylinder
    engraved_cylinder = create_engraved_cylinder(R, L, angle, path_points, "EngravedCylinder")
