# -*- coding: utf-8 -*-

# Macro Begin: C:\Users\v.philippoz\AppData\Roaming\FreeCAD\Macro\sweep_rec2.FCMacro +++++++++++++++++++++++++++++++++++++++++++++++++
import FreeCAD
import Part

# Gui.runCommand('Std_DlgMacroRecord',0)
### Begin command Part_Sweep
from FreeCAD import Base
### End command Part_Sweep
# Gui.Selection.addSelection('Unnamed','Sketch')
# Gui.Selection.removeSelection('Unnamed','Sketch')
# Gui.Selection.addSelection('Unnamed','Sketch001')
# Gui.Selection.removeSelection('Unnamed','Sketch001')
# Gui.Selection.addSelection('Unnamed','Sketch')
# Gui.Selection.clearSelection()
# Gui.Selection.addSelection('Unnamed','Sketch001')
App.getDocument('Unnamed').addObject('Part::Sweep','Sweep')
App.getDocument('Unnamed').ActiveObject.Sections=[App.getDocument('Unnamed').Sketch, ]
App.getDocument('Unnamed').ActiveObject.Spine=(App.getDocument('Unnamed').getObject('Sketch001'),[])
App.getDocument('Unnamed').ActiveObject.Solid=True
App.getDocument('Unnamed').ActiveObject.Frenet=True

# Gui.Selection.clearSelection()
# Macro End: C:\Users\v.philippoz\AppData\Roaming\FreeCAD\Macro\sweep_rec2.FCMacro +++++++++++++++++++++++++++++++++++++++++++++++++
